# -*- coding: utf-8 -*-

import FreeCAD

from pivy import coin

# check if  there is a temporary clipping plane from a previous run of the macro
if hasattr(FreeCAD, 'temporary_sketch_clip_plane'):
	# clipping plane found, remove from scenegraph and delete the object
	Gui.ActiveDocument.ActiveView.getSceneGraph().removeChild(FreeCAD.temporary_sketch_clip_plane)
	del FreeCAD.temporary_sketch_clip_plane

else:
	# no clipping plane found, create one at the sketch base

	# get placement information of the active sketch
	mat  = ActiveSketch.getGlobalPlacement()
	point = mat.Base
	normal = mat.Rotation.multVec(App.Vector(0,0,1))

	# offset of the clipping plane so the sketch elements (lines, etc) are not cut off
	sketch_offset = 0.02		

	# create coin3d vectors of the sketch position	
	coin_normal_vector = coin.SbVec3f(-normal.x, -normal.y, -normal.z)
	coin_base_point = coin.SbVec3f(point.x+sketch_offset, point.y+sketch_offset, point.z+sketch_offset)

	# create the clipping plane at the sketch position
	FreeCAD.temporary_sketch_clip_plane = coin.SoClipPlane()
	FreeCAD.temporary_sketch_clip_plane.plane.setValue(coin.SbPlane(coin_normal_vector,coin_base_point))
	Gui.ActiveDocument.ActiveView.getSceneGraph().insertChild(FreeCAD.temporary_sketch_clip_plane,0)
	
	FreeCAD.temporary_sketch_clip_plane.on.setValue(True) # switch clipping plane on
